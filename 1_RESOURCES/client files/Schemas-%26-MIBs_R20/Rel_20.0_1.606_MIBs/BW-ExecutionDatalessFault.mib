-- File Name : BW-ExecutionDatalessFault.mib

BW-ExecutionDatalessFault DEFINITIONS ::= BEGIN
  IMPORTS
    NOTIFICATION-TYPE, MODULE-IDENTITY
      FROM SNMPv2-SMI
    common, faultFields, identifier, timeStamp, alarmName, systemName, severity, alarmState, component, subcomponent, problemText, recommendedActionsText, correlationParameter, npRemoteAddress, npMessage, npReason, npMethod, npCallId, npDeviceAddress, npOriginator, npHost, npUserId, npMailboxId, npServiceProviderId, npSessionKey, npStackTrace, npEndpointId, npExceptionMessage, npUserUid, npGroupId, npGroupName, npThreadName, npCountryCode, npOldDomainName, npNewDomainName, npUserNumber, npLastIncomingCallTime, npCaller, npTraceType, npGroupNumber, npDirection, npCallingNumber, npCallingNumberContext, npCallingPresentationIndicator, npCalledNumber, npCalledNumberContext, npStartTime, npAnswerTime, npOriginalCalledNumber, npOriginalCalledNumberContext, npOriginalCalledNumberPresentationIndicator, npOriginalCalledReason, npRedirectingNumber, npRedirectingNumberContext, npRedirectingNumberPresentationIndicator, npRedirectingReason, npRoute, npNetworkCallId, npCallingPartyCategory, npCallCapacityGroup, npClientAddress, npSubscriberType, npSubscriberId, npCallType, npDeviceName, npLocalPort, npSmdiNumber, npTimeElapsed, npServerName, npConfiguredAddress, npFailedAttempts, npAllowedAttempts, npResolvedAddress, npCallPersonality, npRemoteParty, npCallAnswered, npFilename, npCallsLimit, npUrl, npNbOfSoapThreads, npPeriod, npPrimaryAddress, npMaximumAttempt, npMaxNumberOfSessions, npRemotePort, npPublicIdentity, npTimeoutValue, npFrom, npSIPCallID, npSCCASPSIDNNumber, npDBSchemaName, npIMRN
      FROM BroadworksFault;

  systemFaults MODULE-IDENTITY
    LAST-UPDATED  "201105020000Z"
    ORGANIZATION  "Broadsoft, Inc"
    CONTACT-INFO  "Broadsoft, Inc.
220 Perry Parkway
Gaithersburg, MD  20877
301-977-9440"
    DESCRIPTION
        "This MIB defines the faults for the Execution Server."
    REVISION    "201105020000Z"
                DESCRIPTION     "Added object 'correlationParameter' in the OBJECTS clause of applicable faults."
    REVISION    "201009140000Z"
                DESCRIPTION     "Moved object 'alarmState' after object 'severity' in the OBJECTS clause of applicable faults."
    REVISION    "200912230000Z"
                DESCRIPTION     "Added faults for FR52198 - Session Data Replication"
    REVISION    "200907200000Z"
                DESCRIPTION     "MIB Creation, based on the defunct BW-ApplicationServerFault.mib."
    ::=  {  common  1  }

  bwPMExecutionDatalessServerLaunched  NOTIFICATION-TYPE
    OBJECTS     { identifier, timeStamp, alarmName, systemName, severity, component, subcomponent, problemText, recommendedActionsText }
    STATUS      current
    DESCRIPTION
        "This notification indicates that the Execution Server has been started.
@severity:informational
@subcomponent:processmonitor
@correlationrules:bwPMExecutionServerLaunched, bwPMExecutionServerShutDown, bwPMExecutionServerRestarted, bwPMExecutionServerDeath, and bwPMExecutionDatalessServerOutOfMemory can be correlated into a single alarm.  These events have to be considered as a transition of the state machine for the management of the Execution Server process running on the BroadWorks Execution Server."
    ::=  {  systemFaults 8901  }

  bwPMExecutionDatalessServerShutDown  NOTIFICATION-TYPE
    OBJECTS     { identifier, timeStamp, alarmName, systemName, severity, component, subcomponent, problemText, recommendedActionsText }
    STATUS      current
    DESCRIPTION
        "This notification indicates that the Execution Server has been manually shut down.
@severity:informational
@subcomponent:processmonitor
@correlationrules:bwPMExecutionServerLaunched, bwPMExecutionServerShutDown, bwPMExecutionServerRestarted, bwPMExecutionServerDeath, and bwPMExecutionDatalessServerOutOfMemory can be correlated into a single alarm.  These events have to be considered as a transition of the state machine for the management of the Execution Server process running on the BroadWorks Execution Server."
    ::=  {  systemFaults 8902  }

  bwPMExecutionDatalessServerRestarted  NOTIFICATION-TYPE
    OBJECTS     { identifier, timeStamp, alarmName, systemName, severity, component, subcomponent, problemText, recommendedActionsText }
    STATUS      current
    DESCRIPTION
        "This notification provides the date and time of the Execution Server restart.
@severity:informational
@subcomponent:processmonitor
@correlationrules:bwPMExecutionServerLaunched, bwPMExecutionServerShutDown, bwPMExecutionServerRestarted, bwPMExecutionServerDeath, and bwPMExecutionDatalessServerOutOfMemory can be correlated into a single alarm.  These events have to be considered as a transition of the state machine for the management of the Execution Server process running on the BroadWorks Execution Server."
    ::=  {  systemFaults 8903  }

  bwPMExecutionDatalessServerDeath  NOTIFICATION-TYPE
    OBJECTS     { identifier, timeStamp, alarmName, systemName, severity, component, subcomponent, problemText, recommendedActionsText }
    STATUS      current
    DESCRIPTION
        "This notification provides the date and time of the Execution Server death.
@severity:critical
@subcomponent:processmonitor
@correlationrules:bwPMExecutionServerLaunched, bwPMExecutionServerShutDown, bwPMExecutionServerRestarted, bwPMExecutionServerDeath, and bwPMExecutionDatalessServerOutOfMemory can be correlated into a single alarm.  These events have to be considered as a transition of the state machine for the management of the Execution Server process running on the BroadWorks Execution Server."
    ::=  {  systemFaults 8904 }


  bwDXSSipAuthenticationFailure  NOTIFICATION-TYPE
    OBJECTS     { identifier, timeStamp, alarmName, systemName, severity, component, subcomponent, problemText, recommendedActionsText, npOriginator, npMessage }
    STATUS      current
    DESCRIPTION
        "Authentication challenge from device failed.
@severity:low
@subcomponent:sip"
    ::=  {  systemFaults 8905  }

  bwDXSAclViolation  NOTIFICATION-TYPE
    OBJECTS     { identifier, timeStamp, alarmName, systemName, severity, component, subcomponent, problemText, recommendedActionsText, npMethod, npCallId, npReason }
    STATUS      current
    DESCRIPTION
        "SIP request received from an unknown device.
@severity:low
@subcomponent:sip"
    ::=  {  systemFaults 8906  }

  bwDXSIMSRetrieveMessageError  NOTIFICATION-TYPE
    OBJECTS     { identifier, timeStamp, alarmName, systemName, severity, component, subcomponent, problemText, recommendedActionsText, npUserId, npMailboxId, npRemoteAddress }
    STATUS      current
    DESCRIPTION
        "This notification indicates a fault that occurred during the retrieval of an e-mail message from the incoming mail server.
@severity:medium
@subcomponent:ims"
    ::=  {  systemFaults 8907  }

  bwDXSIMSRetrieveMailBoxInfoError  NOTIFICATION-TYPE
    OBJECTS     { identifier, timeStamp, alarmName, systemName, severity, component, subcomponent, problemText, recommendedActionsText, npUserId, npRemoteAddress, npUserId, npServiceProviderId }
    STATUS      current
    DESCRIPTION
        "This notification indicates an error retrieving a user's mailbox information from the incoming mail server.
@severity:medium
@subcomponent:ims"
    ::=  {  systemFaults 8908  }

  bwDXSIMSConnectionFailure  NOTIFICATION-TYPE
    OBJECTS     { identifier, timeStamp, alarmName, systemName, severity, alarmState, component, subcomponent, problemText, recommendedActionsText, correlationParameter, npUserId, npMailboxId, npRemoteAddress }
    STATUS      current
    DESCRIPTION
        "This notification indicates a fault occurred during an attempt to connect and log in to the incoming mail server.
@severity:high
@subcomponent:ims"
    ::=  {  systemFaults 8909  }

  bwDXSIMSCloseConnectionError  NOTIFICATION-TYPE
    OBJECTS     { identifier, timeStamp, alarmName, systemName, severity, component, subcomponent, problemText, recommendedActionsText, npUserId, npMailboxId, npRemoteAddress }
    STATUS      current
    DESCRIPTION
        "This notification indicates an unsuccessful attempt to close the current incoming mail server socket connection.
@severity:informational
@subcomponent:ims"
    ::=  {  systemFaults 8910  }

  bwDXSIMSUpdateMailBoxError  NOTIFICATION-TYPE
    OBJECTS     { identifier, timeStamp, alarmName, systemName, severity, component, subcomponent, problemText, recommendedActionsText, npUserId, npMailboxId, npRemoteAddress }
    STATUS      current
    DESCRIPTION
        "This notification indicates an error while marking messages for deletion.
@severity:low
@subcomponent:ims"
    ::=  {  systemFaults 8911  }

  bwDXSMediaServerNotResponding  NOTIFICATION-TYPE
    OBJECTS     { identifier, timeStamp, alarmName, systemName, severity, alarmState, component, subcomponent, problemText, recommendedActionsText, correlationParameter, npRemoteAddress, npSessionKey }
    STATUS      current
    DESCRIPTION
        "A Media Server is not responding to Application Server queries.
@severity:high
@subcomponent:mcp"
    ::=  {  systemFaults 8912  }

  bwDXSMssNetworkServerNotResponding  NOTIFICATION-TYPE
    OBJECTS     { identifier, timeStamp, alarmName, systemName, severity, alarmState, component, subcomponent, problemText, recommendedActionsText, correlationParameter, npRemoteAddress, npSessionKey }
    STATUS      current
    DESCRIPTION
        "A Network Server is not responding to Application Server queries.
@severity:medium
@subcomponent:mss"
    ::=  {  systemFaults 8913  }

  bwDXSMssNoResponse  NOTIFICATION-TYPE
    OBJECTS     { identifier, timeStamp, alarmName, systemName, severity, alarmState, component, subcomponent, problemText, recommendedActionsText, correlationParameter, npRemoteAddress, npSessionKey }
    STATUS      current
    DESCRIPTION
        "None of the Network Servers has responded to Application Server queries.
@severity:high
@subcomponent:mss"
    ::=  {  systemFaults 8914  }

  bwDXSAuditAbnormalCallTermination  NOTIFICATION-TYPE
    OBJECTS     { identifier, timeStamp, alarmName, systemName, severity, component, subcomponent, problemText, recommendedActionsText, npUserUid, npSessionKey, npEndpointId, npDeviceAddress }
    STATUS      current
    DESCRIPTION
        "This notification is sent when an end device does not respond during an active call or when a call is detected in the system in an incorrect state. Session audit has terminated the call when this alarm is sent.
@severity:low
@subcomponent:callp"
    ::=  {  systemFaults 8915  }

  bwDXSEmergencyCallRoutingFailure  NOTIFICATION-TYPE
    OBJECTS     { identifier, timeStamp, alarmName, systemName, severity, component, subcomponent, problemText, recommendedActionsText, npReason }
    STATUS      current
    DESCRIPTION
        "Indicates that there was a problem routing an emergency call to a route.  These are high severity alarms.  A critical alarm is sent if no route could be found or emergency calls cannot be successfully routed.
@severity:high-critical
@subcomponent:emergency"
    ::=  {  systemFaults 8916  }

  bwDXSNetworkRoutingServiceRouteExhaustion  NOTIFICATION-TYPE
    OBJECTS     { identifier, timeStamp, alarmName, systemName, severity, component, subcomponent, problemText, recommendedActionsText, npReason }
    STATUS      current
    DESCRIPTION
        "Indicates that all routes have been exhausted to route a call.
@severity:high-critical
@subcomponent:callp"
    ::=  {  systemFaults 8917  }

  bwDXSCallPThreadAutoRestart  NOTIFICATION-TYPE
    OBJECTS     { identifier, timeStamp, alarmName, systemName, severity, component, subcomponent, problemText, recommendedActionsText, npThreadName }
    STATUS      current
    DESCRIPTION
        "This notification is sent when the Application Server call processing watchdog thread has detected a problem with a call processing thread and has restarted it.
@severity:high
@subcomponent:callp"
    ::=  {  systemFaults 8918  }

  bwDXSForcedExitDueToHungThread  NOTIFICATION-TYPE
    OBJECTS     { identifier, timeStamp, alarmName, systemName, severity, component, subcomponent, problemText, recommendedActionsText, npThreadName }
    STATUS      current
    DESCRIPTION
        "This notification is sent when the Application Server call processing watchdog thread has detected a problem with a call processing thread. An attempt was made to restart the thread, however this has failed.  The Application Server processes exits and is restarted by the process monitor.
@severity:critical
@subcomponent:callp"
    ::=  {  systemFaults 8919  }

  bwDXSOCPMissingCountryCode  NOTIFICATION-TYPE
    OBJECTS     { identifier, timeStamp, alarmName, systemName, severity, component, subcomponent, problemText, recommendedActionsText, npCountryCode }
    STATUS      current
    DESCRIPTION
        "The outgoing calling plan (OCP) file does not contain definitions for a country code that matches the country code of the BroadWorks user performing the origination.
@severity:high
@subcomponent:callp"
    ::=  {  systemFaults 8920  }

  bwDXSSystemDomainNameReset  NOTIFICATION-TYPE
    OBJECTS     { identifier, timeStamp, alarmName, systemName, severity, component, subcomponent, problemText, recommendedActionsText, npOldDomainName, npNewDomainName }
    STATUS      current
    DESCRIPTION
        "Indicates that the system domain was changed.
@severity:high
@subcomponent:transevent"
    ::=  {  systemFaults 8921  }

  bwDXSAccountingFTPConnectionError  NOTIFICATION-TYPE
    OBJECTS     { identifier, timeStamp, alarmName, systemName, severity, alarmState, component, subcomponent, problemText, recommendedActionsText, correlationParameter, npRemoteAddress, npUserId }
    STATUS      current
    DESCRIPTION
        "Problem performing the automatic FTP of the accounting file to the destination FTP server.
@severity:high
@subcomponent:accounting"
    ::=  {  systemFaults 8922  }

  bwDXSCustomerOriginatedTrace  NOTIFICATION-TYPE
    OBJECTS     { identifier, timeStamp, alarmName, systemName, severity, component, subcomponent, problemText, recommendedActionsText, npUserNumber, npLastIncomingCallTime, npCaller, npHost, npCallId }
    STATUS      current
    DESCRIPTION
        "Indicates that a user originated a customer-originated trace (COT) request.
@severity:informational
@subcomponent:callp"
    ::=  {  systemFaults 8923  }

  bwDXSMaliciousCallTrace  NOTIFICATION-TYPE
    OBJECTS     { identifier, timeStamp, alarmName, systemName, severity, component, subcomponent, problemText, recommendedActionsText, npTraceType, npUserNumber, npGroupNumber, npDirection, npCallId, npCallingNumber, npCallingNumberContext, npCallingPresentationIndicator, npCalledNumber, npCalledNumberContext, npStartTime, npAnswerTime, npOriginalCalledNumber, npOriginalCalledNumberContext, npOriginalCalledNumberPresentationIndicator, npOriginalCalledReason, npRedirectingNumber, npRedirectingNumberContext, npRedirectingNumberPresentationIndicator, npRedirectingReason, npRoute, npNetworkCallId, npCallingPartyCategory }
    STATUS      current
    DESCRIPTION
        "Malicious Call Trace is a user service administered by system provider and service provider administrators.  When assigned and active, calls originating from and/or terminating to a user generate an alarm.  The alarm contains a large subset of information listed in a Call Detail Record (for example, calling, called, and redirecting numbers, answer time, and so on) provided the information is available at the moment the alarm is generated.  Malicious Call Trace can be configured in one of three ways:
Answered:  An alarm is generated for all calls terminating on the user only when answered by the user.
Alerting:  An alarm is generated for all calls terminating on the user (answered or not, rejected or not).
All:  An alarm is generated for all of the user's calls (originating and terminating), including originations resulting from a redirection done by the user (such as call forward).
@severity:informational
@subcomponent:callp"
    ::=  {  systemFaults 8924  }

  bwDXSCallCapacityManagementaddCallID  NOTIFICATION-TYPE
    OBJECTS     { identifier, timeStamp, alarmName, systemName, severity, component, subcomponent, problemText, recommendedActionsText, npGroupName, npCallCapacityGroup }
    STATUS      current
    DESCRIPTION
        "The alarm is sent whenever the Call Capacity Management (CCM) feature blocks a call setup attempt because all allocated bandwidth has already been consumed by other calls.  It does not necessarily mean that there is a problem.
@severity:medium
@subcomponent:callp"
    ::=  {  systemFaults 8925  }

  bwDXSSMDIsessionRejected  NOTIFICATION-TYPE
    OBJECTS     { identifier, timeStamp, alarmName, systemName, severity, component, subcomponent, problemText, recommendedActionsText, npReason, npClientAddress }
    STATUS      current
    DESCRIPTION
        "An SMDI session, initiated by an external terminal server, was rejected.
@severity:low
@subcomponent:smdi"
    ::=  {  systemFaults 8926  }

  bwDXSOCPMissingTransferNumber  NOTIFICATION-TYPE
    OBJECTS     { identifier, timeStamp, alarmName, systemName, severity, component, subcomponent, problemText, recommendedActionsText, npSubscriberType, npSubscriberId, npCallType }
    STATUS      current
    DESCRIPTION
        "There is no transfer number provisioned.
@severity:medium
@subcomponent:callp"
    ::=  {  systemFaults 8927  }

  bwDXSOCPMissingAuthorizationCode  NOTIFICATION-TYPE
    OBJECTS     { identifier, timeStamp, alarmName, systemName, severity, component, subcomponent, problemText, recommendedActionsText, npSubscriberType, npSubscriberId, npCallType }
    STATUS      current
    DESCRIPTION
        "There is no authorization code provisioned.
@severity:medium
@subcomponent:callp"
    ::=  {  systemFaults 8928  }

  bwDXSDeviceStatusIsUnavailable  NOTIFICATION-TYPE
    OBJECTS     { identifier, timeStamp, alarmName, systemName, severity, alarmState, component, subcomponent, problemText, recommendedActionsText, correlationParameter, npDeviceAddress }
    STATUS      current
    DESCRIPTION
        "A device is unavailable.
@severity:high
@subcomponent:callp"
    ::=  {  systemFaults 8929  }

  bwDXSSMDIInterfaceError  NOTIFICATION-TYPE
    OBJECTS     { identifier, timeStamp, alarmName, systemName, severity, component, subcomponent, problemText, recommendedActionsText, npLocalPort }
    STATUS      current
    DESCRIPTION
        "The SMDI interface could not be started on a specific port.
@severity:low
@subcomponent:smdi"
    ::=  {  systemFaults 8930  }

  bwDXSSMDIConfigurationError  NOTIFICATION-TYPE
    OBJECTS     { identifier, timeStamp, alarmName, systemName, severity, component, subcomponent, problemText, recommendedActionsText, npUserId, npSmdiNumber }
    STATUS      current
    DESCRIPTION
        "An outgoing SMDI message could not be sent to a SMDI device for the specified user.
@severity:low
@subcomponent:smdi"
    ::=  {  systemFaults 8931  }

  bwDXSSMDIOperationFailure  NOTIFICATION-TYPE
    OBJECTS     { identifier, timeStamp, alarmName, systemName, severity, component, subcomponent, problemText, recommendedActionsText, npUserId, npSmdiNumber, npReason }
    STATUS      current
    DESCRIPTION
        "For the actual description, refer the BroadWorks FaultManagementGuide as it may contain variable data.
@severity:low
@subcomponent:smdi"
    ::=  {  systemFaults 8932  }

  bwDXSSMDIRouteExhaustion  NOTIFICATION-TYPE
    OBJECTS     { identifier, timeStamp, alarmName, systemName, severity, component, subcomponent, problemText, recommendedActionsText, npUserId, npSmdiNumber, npDeviceName }
    STATUS      current
    DESCRIPTION
        "An SMDI message could not be sent because of route exhaustion.
@severity:low
@subcomponent:smdi"
    ::=  {  systemFaults 8933  }

  bwDXSThreadDelayDetected  NOTIFICATION-TYPE
    OBJECTS     { identifier, timeStamp, alarmName, systemName, severity, component, subcomponent, problemText, recommendedActionsText, npThreadName, npTimeElapsed, npMessage }
    STATUS      current
    DESCRIPTION
        "A thread was delayed.
@severity:medium
@subcomponent:callp"
    ::=  {  systemFaults 8934  }

  bwDXSAccountingRadiusServerNotResponding  NOTIFICATION-TYPE
    OBJECTS     { identifier, timeStamp, alarmName, systemName, severity, alarmState, component, subcomponent, problemText, recommendedActionsText, correlationParameter, npServerName, npConfiguredAddress, npResolvedAddress }
    STATUS      current
    DESCRIPTION
        "A Call Detail Server is not responding to write Requests.
@severity:high
@subcomponent:accounting"
    ::=  {  systemFaults 8935  }

  bwDXSAccountingRadiusServersNotConfigured  NOTIFICATION-TYPE
    OBJECTS     { identifier, timeStamp, alarmName, systemName, severity, component, subcomponent, problemText, recommendedActionsText }
    STATUS      current
    DESCRIPTION
        "Sending of the call logs is enabled, but no radius servers are configured.
@severity:high
@subcomponent:accounting"
    ::=  {  systemFaults 8936  }

  bwDXSMaximumFailedVoicePortalLoginAttempts  NOTIFICATION-TYPE
    OBJECTS     { identifier, timeStamp, alarmName, systemName, severity, component, subcomponent, problemText, recommendedActionsText, npFailedAttempts, npAllowedAttempts, npUserId }
    STATUS      current
    DESCRIPTION
        "Triggered when a user is locked out because the maximum number of failed voice portal login attempts is reached.
@severity:informational
@subcomponent:voicePortal"
    ::=  {  systemFaults 8937  }

  bwDXSCallLogRadiusServerUnreachable  NOTIFICATION-TYPE
    OBJECTS     { identifier, timeStamp, alarmName, systemName, severity, alarmState, component, subcomponent, problemText, recommendedActionsText, correlationParameter, npServerName, npConfiguredAddress, npResolvedAddress }
    STATUS      current
    DESCRIPTION
        "A Call Detail Server is not responding to write Requests.
@severity:high
@subcomponent:callLogs"
    ::=  {  systemFaults 8938  }

  bwDXSCallLogRadiusServersNotConfigured  NOTIFICATION-TYPE
    OBJECTS     { identifier, timeStamp, alarmName, systemName, severity, component, subcomponent, problemText, recommendedActionsText }
    STATUS      current
    DESCRIPTION
        "Sending of the call logs is enabled, but no radius servers are configured.
@severity:high
@subcomponent:callLogs"
    ::=  {  systemFaults 8939  }

  bwDXSUserExceededMaxSimultaneousCalls  NOTIFICATION-TYPE
    OBJECTS     { identifier, timeStamp, alarmName, systemName, severity, component, subcomponent, problemText, recommendedActionsText, npCallPersonality, npUserId, npCallId, npRemoteParty }
    STATUS      current
    DESCRIPTION
        "User exceeded the maximum number of simultaneous calls.
@severity:medium
@subcomponent:callp"
    ::=  {  systemFaults 8940  }

  bwDXSUserExceededMaxCallTime  NOTIFICATION-TYPE
    OBJECTS     { identifier, timeStamp, alarmName, systemName, severity, component, subcomponent, problemText, recommendedActionsText, npCallAnswered, npUserId, npCallId, npRemoteParty }
    STATUS      current
    DESCRIPTION
        "User exceeded maximum call time.
@severity:medium
@subcomponent:callp"
    ::=  {  systemFaults 8941  }

  bwDXSInvalidRingbackMediaFile  NOTIFICATION-TYPE
    OBJECTS     { identifier, timeStamp, alarmName, systemName, severity, component, subcomponent, problemText, recommendedActionsText, npFilename, npUserId, npGroupId }
    STATUS      current
    DESCRIPTION
        "Could not ringback file for user.
@severity:medium
@subcomponent:callp"
    ::=  {  systemFaults 8942  }

  bwDXSCallLogRadiusQueueNotProgressing  NOTIFICATION-TYPE
    OBJECTS     { identifier, timeStamp, alarmName, systemName, severity, component, subcomponent, problemText, recommendedActionsText, npRemoteAddress }
    STATUS      current
    DESCRIPTION
        "It has not been possible to send a call log taken from the Application Server file-based queue to a Call Detail Server over the last 60 attempts.
@severity:high
@subcomponent:callLogs"
    ::=  {  systemFaults 8943  }

  bwDXSCallLogRadiusQueueFileDeleted NOTIFICATION-TYPE
    OBJECTS     { identifier, timeStamp, alarmName, systemName, severity, component, subcomponent, problemText, recommendedActionsText, npFilename }
    STATUS      current
    DESCRIPTION
        "A file older than a week has been deleted from the Application Server file-based queue as a safe guard against exhausting the file system space.
@severity:high
@subcomponent:callLogs"
    ::=  {  systemFaults 8944  }

  bwDXSConcurrentCallsExceeded NOTIFICATION-TYPE
    OBJECTS     { identifier, timeStamp, alarmName, systemName, severity, component, subcomponent, problemText, recommendedActionsText, npCallsLimit }
    STATUS      current
    DESCRIPTION
        "A call failed because the number of concurrent calls attempted exceeds the licensed capacity.
@severity:medium
@subcomponent:callp"
    ::=  {  systemFaults 8945  }

  bwDXSENServerUnreachable NOTIFICATION-TYPE
    OBJECTS     { identifier, timeStamp, alarmName, systemName, severity, alarmState, component, subcomponent, problemText, recommendedActionsText, correlationParameter, npRemoteAddress, npExceptionMessage }
    STATUS      current
    DESCRIPTION
        "EN server cannot be reached.
@severity:high
@subcomponent:emergency"
    ::=  {  systemFaults 8946  }

  bwDXSENServerNumberInvalid NOTIFICATION-TYPE
    OBJECTS     { identifier, timeStamp, alarmName, systemName, severity, component, subcomponent, problemText, recommendedActionsText, npCalledNumber }
    STATUS      current
    DESCRIPTION
        "EN server returned an invalid number.
@severity:high
@subcomponent:emergency"
    ::=  {  systemFaults 8947  }

  bwDXSXSOCICommunicationError NOTIFICATION-TYPE
    OBJECTS     { identifier, timeStamp, alarmName, systemName, severity, alarmState, component, subcomponent, problemText, recommendedActionsText, correlationParameter, npMessage }
    STATUS      current
    DESCRIPTION
        "The Execution Server cannot send OCI commands to the Provisioning Server.
@severity:medium
@subcomponent:callp"
    ::=  {  systemFaults 8948  }

  bwDXSUserExceededMaxSimultaneousVideoCalls NOTIFICATION-TYPE
    OBJECTS     { identifier, timeStamp, alarmName, systemName, severity, component, subcomponent, problemText, recommendedActionsText, npCallPersonality, npUserId, npCallId, npRemoteParty }
    STATUS      current
    DESCRIPTION
        "User exceeded the maximum number of simultaneous video calls.
@severity:medium
@subcomponent:callp"
    ::=  {  systemFaults 8949  }

  bwDXSMediaTypeNotSupported NOTIFICATION-TYPE
    OBJECTS     { identifier, timeStamp, alarmName, systemName, severity, component, subcomponent, problemText, recommendedActionsText, npUserId, npEndpointId }
    STATUS      current
    DESCRIPTION
        "The call was rejected because there were no valid media types in the SDP.
@severity:medium
@subcomponent:callp"
    ::=  {  systemFaults 8950  }

  bwDXSENTranslationFailed NOTIFICATION-TYPE
    OBJECTS     { identifier, timeStamp, alarmName, systemName, severity, component, subcomponent, problemText, recommendedActionsText, npUrl }
    STATUS      current
    DESCRIPTION
        "EN translation has failed.
@severity:high
@subcomponent:emergency"
    ::=  {  systemFaults 8951  }

  bwDXSSOAPThreadNumberTooLow NOTIFICATION-TYPE
    OBJECTS     { identifier, timeStamp, alarmName, systemName, severity, component, subcomponent, problemText, recommendedActionsText, npNbOfSoapThreads }
    STATUS      current
    DESCRIPTION
        "The SOAP subsystem could not process requests because the number of threads is too low.  This alarm can only be thrown once, until the server is restarted.
@severity:high
@subcomponent:soap"
    ::=  {  systemFaults 8952  }

  bwDXSUserExceededMaxConcurrentRedirectedCalls NOTIFICATION-TYPE
    OBJECTS     { identifier, timeStamp, alarmName, systemName, severity, component, subcomponent, problemText, recommendedActionsText, npRemoteParty, npUserId, npCallId }
    STATUS      current
    DESCRIPTION
        "Maximum number of concurrent redirected calls exceeded.
@severity:high
@subcomponent:callp"
    ::=  {  systemFaults 8953  }

  bwDXSUserExceededMaxFindMeFollowMeDepth NOTIFICATION-TYPE
    OBJECTS     { identifier, timeStamp, alarmName, systemName, severity, component, subcomponent, problemText, recommendedActionsText, npRemoteParty, npUserId, npCallId }
    STATUS      current
    DESCRIPTION
        "Depth of Find Me/Follow Me chaining exceeded.
@severity:high
@subcomponent:callp"
    ::=  {  systemFaults 8954  }

  bwDXSUserExceededMaxRedirectionDepth NOTIFICATION-TYPE
    OBJECTS     { identifier, timeStamp, alarmName, systemName, severity, component, subcomponent, problemText, recommendedActionsText, npRemoteParty, npUserId, npCallId }
    STATUS      current
    DESCRIPTION
        "Redirection depth limit exceeded.
@severity:high
@subcomponent:callp"
    ::=  {  systemFaults 8955  }

  bwDXSUserExceededMaxFindMeFollowMeInvocations NOTIFICATION-TYPE
    OBJECTS     { identifier, timeStamp, alarmName, systemName, severity, component, subcomponent, problemText, recommendedActionsText, npRemoteParty, npUserId, npCallId }
    STATUS      current
    DESCRIPTION
        "Maximum number of concurrent Find Me/Follow Me invocations exceeded.
@severity:high
@subcomponent:callp"
    ::=  {  systemFaults 8956  }

  bwDXSForwardDestinationLoop NOTIFICATION-TYPE
    OBJECTS     { identifier, timeStamp, alarmName, systemName, severity, component, subcomponent, problemText, recommendedActionsText, npRemoteParty, npUserId, npCallId }
    STATUS      current
    DESCRIPTION
        "Forwarding loop detected.
@severity:high
@subcomponent:callp"
    ::=  {  systemFaults 8957  }

  bwDXSSmppRoutesExhausted NOTIFICATION-TYPE
    OBJECTS     { identifier, timeStamp, alarmName, systemName, severity, alarmState, component, subcomponent, problemText, recommendedActionsText, correlationParameter }
    STATUS      current
    DESCRIPTION
        "Cannot connect to any provisioned SMS-C. All MWI to mobile notifications are lost. This alarm is cleared by the Application Server once connection can be re-established.
@severity:high
@subcomponent:smpp"
    ::= { systemFaults 8958 }

--  bwDXSCongestionManagementNeighborOverloaded moved to BroadWorksFault in 17.ps3 as bwCongestionManagementNeighborOverloaded
--    ::= { systemFaults 8959 }

--  bwDXSDnsServerUnreachable moved to BroadWorksFault in 17.ps3 as bwDnsServerUnreachable
--    ::= { systemFaults 8960 }

--  bwDXSDnsAllServersUnreachable moved to BroadWorksFault in 17.ps3 as bwDnsAllServersUnreachable
--    ::= { systemFaults 8961 }

  bwDXSEmergencyCallOriginated   NOTIFICATION-TYPE
    OBJECTS     { identifier, timeStamp, alarmName, systemName, severity, component, subcomponent, problemText, recommendedActionsText, npUserId }
    STATUS      current
    DESCRIPTION
        "An emergency call origination has been performed.
@severity:informational
@subcomponent:emergency"
    ::= { systemFaults 8962 }

  bwDXSSmppConnectionFailure NOTIFICATION-TYPE
    OBJECTS     { identifier ,timeStamp ,alarmName ,systemName, severity, alarmState ,component ,subcomponent ,problemText ,recommendedActionsText, correlationParameter }
    STATUS      current
    DESCRIPTION
        "A connection attempt (initial connection attempt on first SMS event, new connection after inactivity, or reconnection after unexpected connection close) failed or an open SMPP connection unexpectedly closed (due to network, peer, or other unknown reason).
@severity:low
@subcomponent:smpp
@correlationrules:This alarm is cleared by the Application Server once connection is re-established or reconfigured."
    ::= { systemFaults 8963 }

  bwDXSCommunicationBarringUserLockedOut NOTIFICATION-TYPE
    OBJECTS     { identifier, timeStamp, alarmName, systemName, severity, component, subcomponent, problemText, recommendedActionsText, npMaximumAttempt, npUserId }
    STATUS      current
    DESCRIPTION
        "The server detected repeated attempts by a user to activate or deactivate Communication Barring with an erroneous pin code or without a PIN.
@severity:low
@subcomponent:callp"
    ::= { systemFaults 8964 }

  bwDXSMaxSessionsReached NOTIFICATION-TYPE
    OBJECTS     { identifier, timeStamp, alarmName, systemName, severity, component, subcomponent, problemText, recommendedActionsText, npMaxNumberOfSessions, npSubscriberId }
    STATUS      current
    DESCRIPTION
        "The maximum number of sessions has been reached for the given subscriber level Id (SP / Ent or Group).
@severity:medium
@subcomponent:callp"
    ::= { systemFaults 8965 }

  bwDXSMaxOrigSessionsReached NOTIFICATION-TYPE
    OBJECTS     { identifier, timeStamp, alarmName, systemName, severity, component, subcomponent, problemText, recommendedActionsText, npMaxNumberOfSessions, npSubscriberId }
    STATUS      current
    DESCRIPTION
        "The maximum number of originating sessions has been reached for the given subscriber level Id (SP / Ent or Group).
@severity:medium
@subcomponent:callp"
    ::= { systemFaults 8966 }

  bwDXSMaxTermSessionsReached NOTIFICATION-TYPE
    OBJECTS     { identifier, timeStamp, alarmName, systemName, severity, component, subcomponent, problemText, recommendedActionsText, npMaxNumberOfSessions, npSubscriberId }
    STATUS      current
    DESCRIPTION
        "The maximum number of terminating sessions has been reached for the given subscriber level Id (SP / Ent or Group).
@severity:medium
@subcomponent:callp"
    ::= { systemFaults 8967 }

  bwDXSXsInternalPeerConnectionFailure NOTIFICATION-TYPE
    OBJECTS     { identifier, timeStamp, alarmName, systemName, severity, alarmState, component, subcomponent, problemText, recommendedActionsText, correlationParameter, npServerName, npRemoteAddress, npRemotePort }
    STATUS      current
    DESCRIPTION
        "A failure occurred on the internal Diameter connection to the PS.
@severity:high
@subcomponent:diameter
@correlationrules:This alarm is cleared by the once connection is re-established or reconfigured."
    ::= { systemFaults 8968 }

  bwDXSXsExternalPeerConnectionFailure NOTIFICATION-TYPE
    OBJECTS     { identifier, timeStamp, alarmName, systemName, severity, alarmState, component, subcomponent, problemText, recommendedActionsText, correlationParameter, npServerName, npRemoteAddress, npRemotePort }
    STATUS      current
    DESCRIPTION
        "A failure occurred on a connection between the XS and a Diameter Peer.
@severity:high
@subcomponent:diameter
@correlationrules:This alarm is cleared by the once connection is re-established or reconfigured."
    ::= { systemFaults 8969 }

  bwDXSXsInternalInterfaceInitializationError NOTIFICATION-TYPE
    OBJECTS     { identifier, timeStamp, alarmName, systemName, severity, component, subcomponent, problemText, recommendedActionsText, npExceptionMessage }
    STATUS      current
    DESCRIPTION
        "The Diameter Interface cannot be initialized. 
@severity:high
@subcomponent:diameter"
    ::= { systemFaults 8970 }

  bwDXSXsExternalInterfaceInitializationError NOTIFICATION-TYPE
    OBJECTS     { identifier, timeStamp, alarmName, systemName, severity, component, subcomponent, problemText, recommendedActionsText, npExceptionMessage }
    STATUS      current
    DESCRIPTION
        "The Diameter Interface cannot be initialized. 
@severity:high
@subcomponent:diameter"
    ::= { systemFaults 8971 }

  bwDXSRfFailureTemporaryCondition NOTIFICATION-TYPE
    OBJECTS { identifier, timeStamp, alarmName, systemName, severity, component, subcomponent, problemText, recommendedActionsText, npReason, npRemoteAddress, npUserId, npCallId }
    STATUS      current
    DESCRIPTION
        "A temporary failure prevented an Accounting Request from being delivered over Diameter.  If file queuing is enabled, this request is attempted again later.
@severity:high
@subcomponent:accounting"
    ::= { systemFaults 8972 }

  bwDXSRfFailurePermanentCondition NOTIFICATION-TYPE
    OBJECTS { identifier, timeStamp, alarmName, systemName, severity, component, subcomponent, problemText, recommendedActionsText, npReason, npRemoteAddress, npUserId, npCallId }
    STATUS      current
    DESCRIPTION
        "A permanent failure prevented an Accounting Request from being delivered over Diameter.  This request was discarded.
@severity:high
@subcomponent:accounting"
    ::= { systemFaults 8973 }

  bwDXSRfBacklogQueueNotProgressing NOTIFICATION-TYPE
    OBJECTS { identifier, timeStamp, alarmName, systemName, severity, alarmState, component, subcomponent, problemText, recommendedActionsText, correlationParameter, npPrimaryAddress }
    STATUS      current
    DESCRIPTION
        "It has not been possible to send a request taken from the Application Server file-based queue to an offline charging server over the last 60 or more attempts.
@severity:high
@subcomponent:accounting"
    ::= { systemFaults 8974 }

  bwDXSRfBacklogQueueFileDeleted NOTIFICATION-TYPE
    OBJECTS { identifier, timeStamp, alarmName, systemName, severity, component, subcomponent, problemText, recommendedActionsText, npFilename, npPrimaryAddress }
    STATUS      current
    DESCRIPTION
        "A file older than the configured value has been deleted from the Application Server file-based queue for the Diameter offline charging interface as a safe guard against exhausting the file system space. File content may have been partially transmitted.
@severity:high
@subcomponent:accounting"
    ::= { systemFaults 8975 }

  bwDXSRfBacklogQueuingDisabled  NOTIFICATION-TYPE
    OBJECTS { identifier, timeStamp, alarmName, systemName, severity, component, subcomponent, problemText, recommendedActionsText }
    STATUS      current
    DESCRIPTION
        "The disk is too full to continue file queuing of ACR requests. File queuing has been disabled automatically.
@severity:high
@subcomponent:accounting"
    ::= { systemFaults 8976 }

  bwDXSRoFailureTemporaryCondition NOTIFICATION-TYPE
    OBJECTS { identifier, timeStamp, alarmName, systemName, severity, component, subcomponent, problemText, recommendedActionsText, npReason, npRemoteAddress, npUserId, npCallId }
    STATUS      current
    DESCRIPTION
        "A temporary failure prevented an online credit control request from being delivered over Diameter.
@severity:high
@subcomponent:accounting"
    ::= { systemFaults 8977 }

  bwDXSRoFailurePermanentCondition NOTIFICATION-TYPE
    OBJECTS { identifier, timeStamp, alarmName, systemName, severity, component, subcomponent, problemText, recommendedActionsText, npReason, npRemoteAddress, npUserId, npCallId }
    STATUS      current
    DESCRIPTION
        "A permanent failure prevented an online credit control request from being delivered over Diameter.  This request was discarded.
@severity:high
@subcomponent:accounting"
    ::= { systemFaults 8978 }

  bwDXSTimeoutLoadingProfile NOTIFICATION-TYPE
    OBJECTS { identifier, timeStamp, alarmName, systemName, severity, component, subcomponent, problemText, recommendedActionsText, npPublicIdentity, npTimeoutValue }
    STATUS      current
    DESCRIPTION
        "A timeout occurred while trying to load a subscriber profile from remote storage.
@severity:medium
@subcomponent:callp"
    ::= { systemFaults 8979 }

  bwDXSErrorLoadingProfile NOTIFICATION-TYPE
    OBJECTS { identifier, timeStamp, alarmName, systemName, severity, component, subcomponent, problemText, recommendedActionsText, npPublicIdentity }
    STATUS      current
    DESCRIPTION
        "There was an error retrieving a subscriber profile from remote storage. This profile was either missing or was not formatted properly.
@severity:medium
@subcomponent:callp"
    ::= { systemFaults 8980 }

  bwDXSSCCASPSIDNAllocationFailed NOTIFICATION-TYPE
    OBJECTS { identifier, timeStamp, alarmName, systemName, severity, component, subcomponent, problemText, recommendedActionsText, npReason }
    STATUS      current
    DESCRIPTION
        "This notification is generated when the Execution Server fails to allocate an SCC AS PSI DN.
@severity:high
@subcomponent:callp"
    ::= { systemFaults 8981 }

  bwDXSSCCASPSIDNAllocationTimeOut NOTIFICATION-TYPE
    OBJECTS { identifier, timeStamp, alarmName, systemName, severity, component, subcomponent, problemText, recommendedActionsText, npSCCASPSIDNNumber, npUserId }
    STATUS      current
    DESCRIPTION
        "This notification is generated when Execution Server times out on a previously allocated SCC AS PSI DN, i.e., does not receive request within 10 seconds.
@severity:informational
@subcomponent:callp"
    ::= { systemFaults 8982 }

  bwDXSSCCASPSIDNAllocationNotFound NOTIFICATION-TYPE
    OBJECTS { identifier, timeStamp, alarmName, systemName, severity, component, subcomponent, problemText, recommendedActionsText, npSCCASPSIDNNumber, npSIPCallID, npFrom }
    STATUS      current
    DESCRIPTION
        "This notification is generated when Execution Server fails to find an SCC AS PSI DN allocation for an incoming request to an SCC AS PSI DN. 
@severity:informational
@subcomponent:callp"
    ::= { systemFaults 8983 }

  bwDXSCallLogReportingOverload NOTIFICATION-TYPE
    OBJECTS { identifier, timeStamp, alarmName, systemName, severity, alarmState, component, subcomponent, problemText, recommendedActionsText, npDBSchemaName }
    STATUS      current
    DESCRIPTION
        "This alarm indicates that centralized database reporting is unable to keep up with call log inflow.  The alarm thresholds are:
Medium:  Connectivity to the database exists, but memory-based queues have reached 75% capacity.
High:  Connectivity to the database is down or memory-based queues have reached maximum capacity.  Call log event data is being persisted to the local file system for later recovery.
Critical:  Data for new calls is being dropped.  The cause could be due to a burst of traffic, whereby new events must be shed because the queues are full, or the cause could be that the file space configured for call log event data has been consumed. 
@severity:medium, high, critical
@subcomponent:callLogs"
-- @feature:117143
    ::= { systemFaults 8984 }


  bwPMExecutionDatalessServerOutOfMemory  NOTIFICATION-TYPE
    OBJECTS     { identifier, timeStamp, alarmName, systemName, severity, component, subcomponent, problemText, recommendedActionsText }
    STATUS      current
    DESCRIPTION
        "This notification provides the date and time when the Execution Server ran out of memory.
@severity:high
@subcomponent:processmonitor
@correlationrules:bwPMExecutionServerLaunched, bwPMExecutionServerShutDown, bwPMExecutionServerRestarted, bwPMExecutionServerDeath, and bwPMExecutionDatalessServerOutOfMemory can be correlated into a single alarm.  These events have to be considered as a transition of the state machine for the management of the Execution Server process running on the BroadWorks Application Server."
-- @feature:165352
    ::=  {  systemFaults 8985 }

  bwDXSExternalCustomRingbackServerFailure NOTIFICATION-TYPE
    OBJECTS { identifier, timeStamp, alarmName, systemName, severity, component, subcomponent, problemText, recommendedActionsText, npRemoteAddress, npUserId }
    STATUS      current
    DESCRIPTION
        "A failure occurred while attempting to connect to an external custom ringback server. 
@severity:medium
@subcomponent:sip"
-- @feature:159646
    ::= { systemFaults 8986 }

  bwDXSSCCIMRNAllocationFailed NOTIFICATION-TYPE
    OBJECTS { identifier, timeStamp, alarmName, systemName, severity, component, subcomponent, problemText, recommendedActionsText, npReason }
    STATUS      current
    DESCRIPTION
        "This notification is generated when the Execution Server fails to allocate an IMRN. 
@severity:high
@subcomponent:callp"
-- @feature:159744
    ::= { systemFaults 8987 }

  bwDXSSCCIMRNAllocationTimeOut NOTIFICATION-TYPE
    OBJECTS { identifier, timeStamp, alarmName, systemName, severity, component, subcomponent, problemText, recommendedActionsText, npIMRN, npUserId }
    STATUS      current
    DESCRIPTION
        "This notification is generated when Execution Server times out on a previously allocated IMRN, that is, does not receive request within 10 seconds. 
@severity:informational
@subcomponent:callp"
-- @feature:159744
    ::= { systemFaults 8988 }

  bwDXSSCCIMRNAllocationNotFound NOTIFICATION-TYPE
    OBJECTS { identifier, timeStamp, alarmName, systemName, severity, component, subcomponent, problemText, recommendedActionsText, npIMRN, npSIPCallID, npFrom }
    STATUS      current
    DESCRIPTION
        "This notification is generated when Execution Server fails to find an IMRN allocation for an incoming request to an IMRN.
@severity:informational
@subcomponent:callp"
-- @feature:159744
    ::= { systemFaults 8989 }

  bwDXSSCCCSRNFetchFailure NOTIFICATION-TYPE
    OBJECTS { identifier, timeStamp, alarmName, systemName, severity, component, subcomponent, problemText, recommendedActionsText, npReason }
    STATUS      current
    DESCRIPTION
        "This notification is generated when the Execution Server fails to fetch a CSRN from the SCF for terminations breaking out to the CS access network.
@severity:medium
@subcomponent:callp"
-- @feature:159744
    ::= { systemFaults 8990 }


END
